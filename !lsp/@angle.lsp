;zwraca pelen kat
(defun @angle ()
  (setq $p1 (getpoint "Wskaz 1 pkt"))
  (setq $p2 (getpoint "Wskaz 2 pkt"))
  (setq $angle  (@RtD (angle $p2 $p1)))
  (@FIX $angle)
)
(defun @fix ($unfixed)()
(setq $fixed (fix $unfixed))
(setq $delta ( - $unfixed $fixed))
(if (> $delta 0.5)
  (setq $fixed (+ $fixed 1))
)
(print $fixed)
)
