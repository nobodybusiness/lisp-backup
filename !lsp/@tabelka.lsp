(defun c:@tabelka ()
  (vl-load-com)
  (setq $changeOnlyProjAndDate (getstring "Zmiana tylko projektabta i daty <y>"))
  (if (= $changeOnlyProjAndDate "")
    (progn
      (setq $NAZWA_PROJEKTU "s")
      (setq $SKALA "s")
      (setq $NR-RYS "s")
      (setq $inne_oznacz "")
    )
    (progn
      (setq $NAZWA_PROJEKTU (getstring "Nazwa projektu:"))
      (setq $SKALA (getstring "Skala:"))
      (setq $NR-RYS (getstring "nr rys:"))
      (setq $inne_oznacz (strcase (getstring "Inne oznaczenia:<s/null>")))
    )
  )
  (setq $projektant_inicj (strcase (getstring "Projektant:<PK MG MN PP>")))
  (setq $PROJEKTANT nil)
  (setq $PROJEKTANT
    (cond
      ((= $projektant_inicj "PK") "")
      ((= $projektant_inicj "MG") "")
      ((= $projektant_inicj "MN") "")
      (t " ")
    )
  )
  (setq $asystent "")
  (setq d (rtos (getvar "CDATE") 2 6)
    ;get the date and time and convert to text

        yr (strcat "20" (substr d 3 2))
        ;extract the year

        mo (substr d 5 2)
        ;extract the month

        day (substr d 7 2)
        ;extract the day

  )  ;setq
;===========================================
  (setq $blk nil)
  (setq $blk (ssget '((0 . "INSERT") (2 . "Tabelka5"))))
  (setq $VAL 0)
  (setq $ent (ssname $blk 0))
  (setq $name "none")
  (setq $name (cdr (assoc '0 (entget $ent))))
  (while (not (equal $name "SEQEND"))  ;NAZWA PROJEKTU
    (setq $LST (entget $ent))
    (setq $attag (cdr (assoc '2 $LST)))
    (setq $attag (strcase $attag))
    (if (= $attag "PROJEKT1")
      (if (/= $NAZWA_PROJEKTU "s")
        (progn
          (setq $VAL_new $NAZWA_PROJEKTU)
          (setq $VAL (subst (cons 1 $VAL_new) (assoc 1 $LST) $LST))
          (entmod $VAL)
          (entupd $ent)
        )
      )
    )
    (setq $ent (entnext $ent))
    (setq $name (cdr (assoc '0 (entget $ent))))
  )
  (setq $ent (ssname $blk 0))
  (setq $name "none")
  (setq $name (cdr (assoc '0 (entget $ent))))
  (while (not (equal $name "SEQEND"))  ; STALE
    (setq $LST (entget $ent))
    (setq $attag (cdr (assoc '2 $LST)))
    (setq $attag (strcase $attag))
    (if (= $attag "PROJEKT2")
      (progn
        (if (= $inne_oznacz "s")
          (progn
            (setq $VAL_new "Budowa sieci FTTH - Orange Polska S.A.")
            (setq $VAL (subst (cons 1 $VAL_new) (assoc 1 $LST) $LST))
            (entmod $VAL)
            (entupd $ent)
          )
        )
      )
    )
    (setq $ent (entnext $ent))
    (setq $name (cdr (assoc '0 (entget $ent))))
  )
  (setq $ent (ssname $blk 0))
  (setq $name "none")
  (setq $name (cdr (assoc '0 (entget $ent))))
  (while (not (equal $name "SEQEND"))  ; SKALA
    (setq $LST (entget $ent))
    (setq $attag (cdr (assoc '2 $LST)))
    (setq $attag (strcase $attag))
    (if (= $attag "SKALA")
      (if (/= $SKALA "s")
        (progn
          (setq $VAL_new $SKALA)
          (setq $VAL (subst (cons 1 $VAL_new) (assoc 1 $LST) $LST))
          (entmod $VAL)
          (entupd $ent)
        )
      )
    )
    (setq $ent (entnext $ent))
    (setq $name (cdr (assoc '0 (entget $ent))))
  )
  (setq $ent (ssname $blk 0))
  (setq $name "none")
  (setq $name (cdr (assoc '0 (entget $ent))))
  (while (not (equal $name "SEQEND"))  ; NR RYS
    (setq $LST (entget $ent))
    (setq $attag (cdr (assoc '2 $LST)))
    (setq $attag (strcase $attag))
    (if (= $attag "NR-RYS")
      (if (/= $NR-RYS "s")
        (progn
          (setq $VAL_new $NR-RYS)
          (setq $VAL (subst (cons 1 $VAL_new) (assoc 1 $LST) $LST))
          (entmod $VAL)
          (entupd $ent)
        )
      )
    )
    (setq $ent (entnext $ent))
    (setq $name (cdr (assoc '0 (entget $ent))))
  )
  (setq $ent (ssname $blk 0))
  (setq $name "none")
  (setq $name (cdr (assoc '0 (entget $ent))))
  (while (not (equal $name "SEQEND"))  ; PROJEKTANT
    (setq $LST (entget $ent))
    (setq $attag (cdr (assoc '2 $LST)))
    (setq $attag (strcase $attag))
    (if (= $attag "PROJEKTOWAL")
      (progn
        (setq $VAL_new $PROJEKTANT)
        (setq $VAL (subst (cons 1 $VAL_new) (assoc 1 $LST) $LST))
        (entmod $VAL)
        (entupd $ent)
      )
    )
    (setq $ent (entnext $ent))
    (setq $name (cdr (assoc '0 (entget $ent))))
  )
  (setq $ent (ssname $blk 0))
  (setq $name "none")
  (setq $name (cdr (assoc '0 (entget $ent))))
  (while (not (equal $name "SEQEND"))  ; DATA
    (setq $LST (entget $ent))
    (setq $attag (cdr (assoc '2 $LST)))
    (setq $attag (strcase $attag))
    (if (= $attag "DATA-PR")
      (progn
        (setq $VAL_new (strcat day "-" mo "-" yr))
        (setq $VAL (subst (cons 1 $VAL_new) (assoc 1 $LST) $LST))
        (entmod $VAL)
        (entupd $ent)
      )
    )
    (setq $ent (entnext $ent))
    (setq $name (cdr (assoc '0 (entget $ent))))
  )
  (setq $ent (ssname $blk 0))
  (setq $name "none")
  (setq $name (cdr (assoc '0 (entget $ent))))
  (while (not (equal $name "SEQEND"))  ; SPRAWDZIL
    (setq $LST (entget $ent))
    (setq $attag (cdr (assoc '2 $LST)))
    (setq $attag (strcase $attag))
    (if (= $attag "SPRAWDZIL")
      (progn
        (setq $VAL_new "")
        (setq $VAL (subst (cons 1 $VAL_new) (assoc 1 $LST) $LST))
        (entmod $VAL)
        (entupd $ent)
      )
    )
    (setq $ent (entnext $ent))
    (setq $name (cdr (assoc '0 (entget $ent))))
  )

  (setq $ent (ssname $blk 0))
  (setq $name "none")
  (setq $name (cdr (assoc '0 (entget $ent))))
  (while (not (equal $name "SEQEND"))  ; DATA
    (setq $LST (entget $ent))
    (setq $attag (cdr (assoc '2 $LST)))
    (setq $attag (strcase $attag))
    (if (= $attag "DATA-SPR")
      (progn
        (setq $VAL_new (strcat day "-" mo "-" yr))
        (setq $VAL (subst (cons 1 $VAL_new) (assoc 1 $LST) $LST))
        (entmod $VAL)
        (entupd $ent)
      )
    )
    (setq $ent (entnext $ent))
    (setq $name (cdr (assoc '0 (entget $ent))))
  )


  (setq $ent (ssname $blk 0))
  (setq $name "none")
  (setq $name (cdr (assoc '0 (entget $ent))))
  (while (not (equal $name "SEQEND"))  ; asystent
    (setq $LST (entget $ent))
    (setq $attag (cdr (assoc '2 $LST)))
    (setq $attag (strcase $attag))
    (if (= $attag "RYSOWAL")
      (progn
        (setq $VAL_new $asystent)
        (setq $VAL (subst (cons 1 $VAL_new) (assoc 1 $LST) $LST))
        (entmod $VAL)
        (entupd $ent)
      )
    )
    (setq $ent (entnext $ent))
    (setq $name (cdr (assoc '0 (entget $ent))))
  )


  (setq $ent (ssname $blk 0))
  (setq $name "none")
  (setq $name (cdr (assoc '0 (entget $ent))))
  (while (not (equal $name "SEQEND"))  ; DATA
    (setq $LST (entget $ent))
    (setq $attag (cdr (assoc '2 $LST)))
    (setq $attag (strcase $attag))
    (if (= $attag "DATA-RYS")
      (progn
        (setq $VAL_new "")
        (setq $VAL (subst (cons 1 $VAL_new) (assoc 1 $LST) $LST))
        (entmod $VAL)
        (entupd $ent)
      )
    )
    (setq $ent (entnext $ent))
    (setq $name (cdr (assoc '0 (entget $ent))))
  )
)

(defun c:@nr_rys ()

  (setq $blk nil)
  (setq $blk (ssget '((0 . "INSERT") (2 . "Tabelka5"))))
  (setq $VAL 0)
  (setq $ent (ssname $blk 0))
  (setq $name "none")
  (setq $name (cdr (assoc '0 (entget $ent))))
  (setq $nr_rys (getint "Nr_rys:"))
  (if (= $nr_rys 0)
    (setq $prefix (getstring "Prefix:"))
    (progn
      (while (not (equal $name "SEQEND"))
        (setq $LST (entget $ent))
        (setq $attag (cdr (assoc '2 $LST)))
        (setq $attag (strcase $attag))
        (if (= $attag "NR-RYS")
          (progn
            (setq $VAL_new (strcat $prefix (rtos $nr_rys 2 0)))
            (setq $VAL (subst (cons 1 $VAL_new) (assoc 1 $LST) $LST))
            (entmod $VAL)
            (entupd $ent)
          )
        )
        (setq $ent (entnext $ent))
        (setq $name (cdr (assoc '0 (entget $ent))))
      )
    )
  )
)
