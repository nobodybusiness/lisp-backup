;numeracja kolenych wlokien
(defun c:@wkl ()
  (setq $nr_pocz (getint "Nr poczt.:"))
  (setq $pt (getpoint "PKT wstawienia"))
  (setq $n_string "")
  (setq $n 0)
  (while (< $n 12)
    (setq $n_string (rtos (+ $n 1) 2 0))
    (setq $pA (read (strcat "$p" $n_string)))
    (setq $nr_wkl (rtos (+ $n $nr_pocz) 2 0))
    (set $pA $nr_wkl)
    (setq $n (+ 1 $n))
  )
  (command "insert" "nr_wlokien" $pt "" "" "" $p1 $p2 $p3 $p4 $p5 $p6 $p7 $p8 $p9 $p10 $p11 $p12)
)
(defun c:@wl()
	(setq #wl (getint "Nr wlk:"))
	(setq #fullTubes (fix (/ (- #wl 1) 12)))
	(setq #tube (+ 1 #fullTubes))
	(setq #firstInTube (+ (* #fullTubes 12) 1))
	(setq #lastInTube (+ #firstInTube 11))
	(print (strcat "W tubie " (rtos #tube 2 0) " , pierwsze wl. " (rtos #firstInTube 2 0) " , ostatnie wl. " (rtos #lastInTube 2 0)))
	(princ)
)
