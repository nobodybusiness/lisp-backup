;usuwanie zamrozonych warst
(DEFUN @DELFRZ ()
 (PROMPT "\n*ERASE ALL FROZEN ENTITIES BY LAYER(with purge)* ")
 (SETQ LTSRL 1)
 (SETQ LP 1)
 (WHILE LP
  (SETQ LTS (TBLNEXT "LAYER" LTSRL))
  (SETQ LTSRL NIL)
  (SETQ LTSF (CDR (ASSOC 70 LTS)))
  (SETQ LTST (CDR (ASSOC 2 LTS)))
  (SETQ LTSTF (LIST (CONS 8 LTST)))
  (IF (= LTSF 1)
   (PROGN
    (SETQ EBS (SSGET "X" LTSTF))
    (COMMAND "ERASE" EBS "")
    (COMMAND "LAYER" "T" "0" "S" "0" "")
    (COMMAND "PURGE" "LA" LTST "N")
  ));END PROGN/IF LTSF
  (IF (= LTS NIL) (SETQ LP NIL))
 );END LP
 (PRINC)
);END EFEL
