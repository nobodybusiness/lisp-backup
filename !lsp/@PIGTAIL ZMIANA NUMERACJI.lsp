(defun c:@pigtail_zmiana_numeracji ()
  (setq ss (ssget))
	(setq i 0)
	(setq plus_minus (getint "+/-:"))
  (while (< i (sslength ss))
    (setq $VAL 0)
    (setq $ent (ssname ss i))
    (setq $name "none")
    (setq $name (cdr (assoc '0 (entget $ent))))
    (while (not (equal $name "SEQEND"))  ;NAZWA PROJEKTU
      (setq $LST (entget $ent))
      (setq $attag (cdr (assoc '2 $LST)))
      (setq $attag (strcase $attag))
      (if (OR (= $attag "PRZEL_MIESZKANIA") (= $attag "PRZEL_USLUGI"))
        (progn
          (setq $VAL (atoi (cdr (assoc 1 $LST))))
          (setq $VAL_new (+ $VAL plus_minus))
          (setq $VAL (subst (cons 1 (rtos $VAL_new 2 0)) (assoc 1 $LST) $LST))
          (entmod $VAL)
          (entupd $ent)
        )
      )
      (setq $ent (entnext $ent))
      (setq $name (cdr (assoc '0 (entget $ent))))
    )
    (setq i (+ i 1))
  )
)
