(defun c:@Y ()
  (setq $text (entget (ssname (ssget '((0 . "TEXT"))) 0)))
  (setq $dist (getdist "Odleg³osc miedzy elementami:"))
  (setq $end (getint "Do jakiego numeru:"))
  (setq $i (atoi (cdr (assoc 1 $text))))
  (command "_copy" (cdr (assoc -1 $text)) "" "d" (strcat "0,-" (rtos $dist 0 2) ",0"))
  (setq $i (+ $i 1))
  (while (<= $i $end)
    (setq $textToChange (entget (entlast)))
    (print $textToChange)
    (setq x (rtos $i 0 2))
    (entmod (subst (cons 1 x) (assoc 1 $textToChange) $textToChange))
    (command "_copy" (cdr (assoc -1 $textToChange)) "" "d" (strcat "0,-" (rtos $dist 0 2) ",0"))
    (setq $i (+ $i 1))
  )
  (command "_erase" (cdr (assoc -1 (entget (entlast)))) "")
  (princ)
)
(defun c:@textChangePlusOneX ()
  (setq $text (entget (ssname (ssget '((0 . "TEXT"))) 0)))
  (setq $dist (getdist "Odleg³osc miedzy elementami:"))
  (setq $end (getint "Do jakiego numeru:"))
  (setq $i (atoi (cdr (assoc 1 $text))))
  (command "_copy" (cdr (assoc -1 $text)) "" "d" (strcat (rtos $dist 0 2) ",0"  ",0"))
  (setq $i (+ $i 1))
  (while (<= $i $end)
    (setq $textToChange (entget (entlast)))
    (print $textToChange)
    (setq x (rtos $i 0 2))
    (entmod (subst (cons 1 x) (assoc 1 $textToChange) $textToChange))
    (command "_copy" (cdr (assoc -1 $textToChange)) "" "d" (strcat (rtos $dist 0 2) ",0,"  "0"))
    (setq $i (+ $i 1))
  )
  (command "_erase" (cdr (assoc -1 (entget (entlast)))) "")
  (princ)
)
