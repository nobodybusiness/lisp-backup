;szybkie tworzenie mtxt
(defun c:TXTTOMTX ()
  (setq ss (ssget))
  (setq i 0)
	(setq multitext "")
  (while (< i (sslength ss))
    (setq $VAL 0)
    (setq $ent (ssname ss i))
    (setq $name "none")
    (setq $name (cdr (assoc '1 (entget $ent))))
		;(print $name)
		(setq multitext (strcat multitext $name "\n"))
    (setq i (+ i 1))
  )
	(print multitext)
)
