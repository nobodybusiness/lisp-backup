(defun c:@osd_renumeracja ()
  (setq ss (ssget))
  (setq i 0)
  (setq plus_minus (- (getint "od ilu numeracja") 1))
  (while (< i (sslength ss))
    (setq $VAL 0)
    (setq $ent (ssname ss i))
    (setq $name "none")
    (setq $name (cdr (assoc '0 (entget $ent))))
    (while (not (equal $name "SEQEND"))  ;NAZWA PROJEKTU
      (setq $LST (entget $ent))
      (setq $attag (cdr (assoc '2 $LST)))
      (setq $attag (strcase $attag))
      (if (= $attag "NRZL")
        (progn
          (setq $VAL (atoi (substr (cdr (assoc 1 $LST)) (vl-string-search "/" (cdr (assoc 1 $LST))))))
          (setq $VAL_new (+ $VAL plus_minus i))
          (setq $val_new_string (strcat "PE1/" (rtos $VAL_new 2 0)))
          (setq $VAL (subst (cons 1 $val_new_string) (assoc 1 $LST) $LST))
          (entmod $VAL)
          (entupd $ent)
        )
      )
      (setq $ent (entnext $ent))
      (setq $name (cdr (assoc '0 (entget $ent))))
    )
    (setq i (+ i 1))
  )
)
(defun c:@osd_zero_odl ()
  (setq ss (ssget))
  (setq i 0)
  (while (< i (sslength ss))
    (setq $VAL 0)
    (setq $ent (ssname ss i))
    (setq $name "none")
    (setq $name (cdr (assoc '0 (entget $ent))))
    (while (not (equal $name "SEQEND"))  ;NAZWA PROJEKTU
      (setq $LST (entget $ent))
      (setq $attag (cdr (assoc '2 $LST)))
      (setq $attag (strcase $attag))
      (if (OR (= $attag "DLTRAS") (= $attag "DLINSTAL") (= $attag "DLOPT"))
        (progn
          (setq $val_new_string "?-?")
          (setq $VAL (subst (cons 1 $val_new_string) (assoc 1 $LST) $LST))
          (entmod $VAL)
          (entupd $ent)
        )
      )
      (setq $ent (entnext $ent))
      (setq $name (cdr (assoc '0 (entget $ent))))
    )
    (setq i (+ i 1))
  )
)
(defun c:@osd_okr_odl ()
	;ADD MODE TYPES -> FROM EXISTING OSD, ODL OD PKT, TXT
  (setq ss (ssget))
  (setq i 0)
  (while (< i (sslength ss))
    (setq $VAL 0)
    (setq $ent (ssname ss i))
    (setq $name "none")
    (setq $name (cdr (assoc '0 (entget $ent))))
    (setq $odlA (getint "odl tras: "))
    (setq $odlB (getint "odl inst: "))
    (setq $odlC (getint "odl opt: "))
    (while (not (equal $name "SEQEND"))  ;NAZWA PROJEKTU
      (setq $LST (entget $ent))
      (setq $attag (cdr (assoc '2 $LST)))
      (setq $attag (strcase $attag))
      (if (OR (= $attag "DLTRAS") (= $attag "DLINSTAL") (= $attag "DLOPT"))
        (progn
          ;(setq $val_A (getint "odl:"))
          (setq $val_A
            (cond
              ((= $attag "DLTRAS") $odlA)
              ((= $attag "DLINSTAL") $odlB)
              ((= $attag "DLOPT") $odlC)
            )
          )
          (setq $val_B (getint "pktA:"))
          (setq $val_new (+ $val_A $val_B))
          (setq $val_new_string (strcat (rtos $val_A 2 0) "-" (rtos $VAL_new 2 0)))
          (setq $VAL (subst (cons 1 $val_new_string) (assoc 1 $LST) $LST))
          (entmod $VAL)
          (entupd $ent)
        )
      )
      (setq $ent (entnext $ent))
      (setq $name (cdr (assoc '0 (entget $ent))))
    )
    (setq i (+ i 1))
  )
)

(defun c:@osd_okr_odl_calk ()
  (setq ss (ssget))
  (setq i 0)
  (while (< i (sslength ss))
    (setq $VAL 0)
    (setq $ent (ssname ss i))
    (setq $name "none")
    (setq $name (cdr (assoc '0 (entget $ent))))
    (while (not (equal $name "SEQEND"))  ;NAZWA PROJEKTU
      (setq $LST (entget $ent))
      (setq $attag (cdr (assoc '2 $LST)))
      (setq $attag (strcase $attag))
      (if (OR (= $attag "DLTRAS") (= $attag "DLINSTAL") (= $attag "DLOPT"))
        (progn
          (setq $val_A (getint "pktA:"))
          (setq $val_B (getint "pktB:"))
          (setq $val_new (- $val_B $val_A))
          (setq $val_new_string (strcat (rtos $val_new 2 0) "-" (rtos $VAL_B 2 0)))
          (setq $VAL (subst (cons 1 $val_new_string) (assoc 1 $LST) $LST))
          (entmod $VAL)
          (entupd $ent)
        )
      )
      (setq $ent (entnext $ent))
      (setq $name (cdr (assoc '0 (entget $ent))))
    )
    (setq i (+ i 1))
  )
)

(defun c:@osd_odl_plik ()
  (setq $odl_adress "C:/Users/signaline.pl/Desktop/Piotr P/test/Signaline/ODLEGLOSCI_PKT_OSD/")
  (setq $data nil)
  (setq $filepath $odl_adress)           ; ustawia sciezke do folderu mieszkan
  (setq $fl (open (strcat $filepath "odl.txt") "r"))  ; otwarcie do odczytania pliku z danymi
  (while (setq $fil (read-line $fl))           ;petla do odczytu linni
    (if (not (null $fil))
      (setq $data (append $data (list $fil)))  ; przypisanie  danych do listy
    )
  )
  (close $fl)  ; zamkniecie pliku txt

  (setq ss (ssget))
  (setq i 0)
  (while (< i (sslength ss))
    (setq $VAL 0)
    (setq $ent (ssname ss i))
    (setq $name "none")
    (setq $name (cdr (assoc '0 (entget $ent))))
    (while (not (equal $name "SEQEND"))  ;NAZWA PROJEKTU
      (setq $LST (entget $ent))
      (setq $attag (cdr (assoc '2 $LST)))
      (setq $attag (strcase $attag))
      (if (OR (= $attag "DLTRAS") (= $attag "DLINSTAL") (= $attag "DLOPT"))
        (progn
          (setq $data_str (car $data))
          (setq $val_new_string (vl-string-subst "" "\"" (vl-string-subst "" "\"" (vl-string-subst "-" ";" $data_str))))
          (setq $VAL (subst (cons 1 $val_new_string) (assoc 1 $LST) $LST))
          (entmod $VAL)
          (entupd $ent)
          (setq $data (cdr $data))
        )
      )
      (setq $ent (entnext $ent))
      (setq $name (cdr (assoc '0 (entget $ent))))
    )
    (setq i (+ i 1))
  )
)

(defun c:@osd_kopiuj_wartosci ()
  (setq ss (ssget))
  (setq i 0)
  (setq dataList (list))
  (while (< i (sslength ss))
    (setq $VAL 0)
    (setq $ent (ssname ss i))
    (setq $name "none")
    (setq $name (cdr (assoc '0 (entget $ent))))
    (while (not (equal $name "SEQEND"))  ;NAZWA PROJEKTU
      (setq $LST (entget $ent))
      (setq $attag (cdr (assoc '2 $LST)))
      (setq $attag (strcase $attag))
      (if (OR (= $attag "DLTRAS") (= $attag "DLINSTAL") (= $attag "DLOPT"))
        (progn
          (setq $VAL (cdr (assoc 1 $LST)))
          (setq dataList (append dataList (list $VAL)))
        )
      )
      (setq $ent (entnext $ent))
      (setq $name (cdr (assoc '0 (entget $ent))))
    )
    (setq i (+ i 1))
  )
	
	
  (setq ss (ssget))
  (setq i 0)
  (while (< i (sslength ss))
    (setq $VAL 0)
    (setq $ent (ssname ss i))
    (setq $name "none")
    (setq $name (cdr (assoc '0 (entget $ent))))
    (while (not (equal $name "SEQEND"))  ;NAZWA PROJEKTU
      (setq $LST (entget $ent))
      (setq $attag (cdr (assoc '2 $LST)))
      (setq $attag (strcase $attag))
      (if (OR (= $attag "DLTRAS") (= $attag "DLINSTAL") (= $attag "DLOPT"))
        (progn
          (setq $val_new_string (car dataList))
          (setq $VAL (subst (cons 1 $val_new_string) (assoc 1 $LST) $LST))
          (entmod $VAL)
          (entupd $ent)
          (setq dataList (cdr dataList))
        )
      )
      (setq $ent (entnext $ent))
      (setq $name (cdr (assoc '0 (entget $ent))))
    )
    (setq i (+ i 1))
  )
  )
