;tworzenie layoutow
(defun c:@viewport_trasa ()
  (setq scaleType nil)
  (setq testScale nil)
  (while (/= testScale T)
    (setq scaleType (getstring "<S>chemat,<T>rasowy,<R>zut: "))
    (if (or (= scaleType "s") (= scaleType "t") (= scaleType "r"))
      (setq testScale T)
    )
  )
  (@ALL_VIEWPORTS)
  (setq $layoutstart_value (getint "numer utworzonego layoutu startowego"))
  (setq $layoutstart (rtos $layoutstart_value 2 0))
  (@GOTO_LAYOUT $layoutstart)
  (while $names
    (setq $name (car $names))
    (@VIEWPORT_ZOOM_TO_ONE_BY_HANDLE $name)
    (@COPYLAYOUT)
    (@GOTO_LAYOUT $layout_name_new)
    (setq $names (cdr $names))
  )
  (command "layout" "_d" "")
  (@CHANGESCALEOFALLVIEWPORTS)
)


(defun @all_viewports ()
  (vl-load-com)
  (setq $viewports_selection (ssget '((0 . "LWPOLYLINE") (8 . "viewports"))))
  (setq $i 0)
  (setq $names (list))
  (setq $number_of_elements_in_selection (sslength $viewports_selection))
  (while (< $i $number_of_elements_in_selection)
    (setq $ent (ssname $viewports_selection $i))
    (setq $names (append $names (list $ent)))
    (setq $i (+ 1 $i))
  )
  (print $names)
)
(defun @copylayout ()
  (setq $layout_name (getvar 'ctab))
  (setq $layout_name_value (atoi $layout_name))
  (setq $layout_name_new_value (+ 1 $layout_name_value))
  (setq $layout_name_new (rtos $layout_name_new_value 2 0))
  (command "._layout" "_c" $layout_name $layout_name_new)
)
(defun @goto_layout ($layout_to_go)
  (setvar 'CTab $layout_to_go)
)
(defun @viewport_zoom_to_one_by_handle (x)
  (command "mspace"
           "zoom" "_e"
           "zoom" "_ob" x
  )
  (princ)
  (command "zoom" "_s" "1.019999999999999999")
  (command "._pspace")
)
(defun @ChangeScaleOfAllViewports ()
  (setq get (ssget "x" '((0 . "viewport") (-4 . ">") (69 . 1))))
  (setq $ent_ename (ssname get 0))
  (setq $ent_data (entget $ent_ename))
  (setq heightInPaper (cdr (assoc 41 $ent_data)))
  (setq viewHeight (cdr (assoc 45 $ent_data)))

  (cond
    ((= scaleType "s") (setq scaleTypeValue 0.2))
    ((= scaleType "t") (setq scaleTypeValue 2))
    ((= scaleType "r") (setq scaleTypeValue 0.1))
  )

  (setq scale (/ (* scaleTypeValue viewHeight) heightInPaper))
  (foreach lay (layoutlist) (setvar "CTAB" lay) (command "mspace" "zoom" "_s" scale "._pspace"))

)
