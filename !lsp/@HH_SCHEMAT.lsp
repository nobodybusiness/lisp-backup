;tworzenie calej jednej mufy z adresow zaznaczonych
(defun c:@HH_SCHEMAT ()
  (vl-load-com)
  (setq ss (ssget))
  (setq i 0)
  (setq $VAL "")
  (setq fromTop 0)  ;nr HH od g�ry
  (setq pta (getpoint "PKT wstawienia:"))
  (while (< i (sslength ss))
    ;#ulice
    (setq $VAL "")
    (setq $ent (ssname ss i))
    (setq $name "none")
    (setq $name (cdr (assoc '0 (entget $ent))))
    (while (not (equal $name "SEQEND"))
      (setq $LST (entget $ent))
      (setq $attag (cdr (assoc '2 $LST)))
      (setq $attag (strcase $attag))
      (if (= $attag "ULICA")
        (setq $VAL (substr (cdr (assoc 1 $LST)) (+ 3 (vl-string-search "." (cdr (assoc 1 $LST))))))
      )
      (setq $ent (entnext $ent))
      (setq $name (cdr (assoc '0 (entget $ent))))
    )
    ;#ulice
    ;#HH
    (setq HHandLUvalue 1)
    (setq $ent (ssname ss i))
    (setq $name "none")
    (setq $name (cdr (assoc '0 (entget $ent))))
    (while (not (equal $name "SEQEND"))
      (setq $LST (entget $ent))
      (setq $attag (cdr (assoc '2 $LST)))
      (setq $attag (strcase $attag))
      (if (= $attag "HH")
        (if (not (equal "HH:1" (cdr (assoc 1 $LST))))
          (progn
            (setq HHandLU (cdr (assoc 1 $LST)))
            (setq $val (strcat $VAL " (" HHandLU ")"))
            (setq HHandLUvalue 0)
            (setq asciiHHandLu (vl-string->list HHandLU))
            (foreach n asciiHHandLu
              (if (and (>= n 48) (<= n 57))
                (setq HHandLUvalue (+ HHandLUvalue (- n 48)))
              )
            )
          )
        )
      )
      (setq $ent (entnext $ent))
      (setq $name (cdr (assoc '0 (entget $ent))))
    )
    ;#HH
    (setq ptx (rtos (car pta) 2 6))
    (setq pty (rtos (- (cadr pta) (* fromTop 15.6)) 2 6))
    (setq ptz (rtos (caddr pta) 2 6))
    (setq ptb (strcat ptx "," pty "," ptz))
    (command "-insert" (strcat "ULICA_NR_HH_" (itoa HHandLUvalue)) ptb "" "" "" $VAL)
    (command "@burst" "_L" "")
    (setq i (+ i 1))
		(setq fromTop (+ fromTop HHandLUvalue))
  )
  (command "explode" pause)
)
(defun c:@usuwanie_attdef ()
  (setq ss (ssget "all" '((0 . "ATTDEF"))))
  (command "_erase" ss "")
)
(defun c:@test ()
  (setq i 1)
  (setq st "test_")
  (setq sti (strcat st (itoa i)))
)
