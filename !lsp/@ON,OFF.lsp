;widoczność warstw
(defun @OFF ()
  (setq $selected_layers (ssget))
  (setq $i 0)
  (setq $zaznaczenie 0)
  (command "-layer" "_of" "" "_y" "")
  (while $zaznaczenie
    (setq $zaznaczenie (ssname $selected_layers $i))
    (setq $warstwa (cdr (assoc 8 (entget $zaznaczenie))))
    (command "-layer" "_on" $warstwa "")
    (princ) 
    (setq $i (1+ $i))
  )
  (princ)
)

(defun @OFF_BASE_FUNCTION ($selected_layers)
  (setq $i 0)
  (setq $zaznaczenie 0)
  (command "-layer" "_of" "" "_y" "")
  (while $zaznaczenie
    (setq $zaznaczenie (ssname $selected_layers $i))
    (setq $warstwa (cdr (assoc 8 (entget $zaznaczenie))))
    (command "-layer" "_on" $warstwa "")
    (princ) 
    (setq $i (1+ $i))
  )
  (princ)
)

(defun @OFF_BASE()
  (@OFF_BASE_FUNCTION $selected_layers_for_function)
)

(defun @base ()
  (setq $selected_layers_for_function (ssget))
)

(defun @ON ()
  (command "-layer" "_on" "" "_y" "")
)
(defun @OFF_one ()
  (setq $selected_layers (ssget))
  (setq $i 0)
  (setq $zaznaczenie 0)
  (while $zaznaczenie
    (setq $zaznaczenie (ssname $selected_layers $i))
    (setq $warstwa (cdr (assoc 8 (entget $zaznaczenie))))
    (command "-layer" "_of" $warstwa "_y" "")
    (setq $i (1+ $i))
  )
  (princ)
)
(defun @lock ()
  (setq $selected_layers (ssget))
  (setq $i 0)
  (setq $zaznaczenie 0)
  (while $zaznaczenie
    (setq $zaznaczenie (ssname $selected_layers $i))
    (setq $warstwa (cdr (assoc 8 (entget $zaznaczenie))))
    (command "-layer" "_lo" $warstwa "_y" "")
    (setq $i (1+ $i))
  )
  (princ)
)
(defun @lock_all ()
  (command "-layer" "_lo" "" "_y" "")
)
(defun @unlock_all ()
  (command "-layer" "_un" "" "_y" "")
)
(defun @unlock ()
  (setq $selected_layers (ssget))
  (setq $i 0)
  (setq $zaznaczenie 0)
  (while $zaznaczenie
    (setq $zaznaczenie (ssname $selected_layers $i))
    (setq $warstwa (cdr (assoc 8 (entget $zaznaczenie))))
    (command "-layer" "_un" $warstwa "_y" "")
    (setq $i (1+ $i))
  )
  (princ)
)
(defun @freeze ()
  (setq $selected_layers (ssget))
  (setq $i 0)
  (setq $zaznaczenie (ssname $selected_layers $i))
  (while $zaznaczenie
    (setq $zaznaczenie (ssname $selected_layers $i))
    (setq $warstwa (cdr (assoc 8 (entget $zaznaczenie))))
    (command "-layer" "_f" $warstwa "_y" "")
    (setq $i (1+ $i))
  )
  (princ)
)
(defun @unfreeze ()
  (command "-layer" "_t" "" "_y" "")
)
(defun c:@layer_select()
 (setq TargEnt (car (entsel "\nSelect object on layer to select: ")))
 (setq TargLayer (assoc 8 (entget TargEnt)))
 (sssetfirst nil (ssget "_X" (list TargLayer)))
 (princ)
)

(defun c:@freeze_map()
  (command "-layer" "_f" "mapa" "_y" "")
)
(defun c:@unfreeze_map()
  (command "-layer" "_t" "mapa" "_y" "")
)

(defun c:@nr_studni_magistrala_on()
  (command "-layer" "_f" "pkt_adresy_hh" "")
)
(defun c:@nr_studni_magistrala_off()
  (command "-layer" "_t" "pkt_adresy_hh" "")
)

(defun c:@viewports_on()
  (command "-layer" "_f" "VIEWPORTS" "")
)
(defun c:@viewports_off()
  (command "-layer" "_t" "VIEWPORTS" "")
)

(DEFUN C:XLO ( / lay) (PRINC "\nXref layer off")
(WHILE (princ (strcat "\nTurned off " (setq LAY (cdr (assoc 8 (entget (car (NENTSEL "\nSelect item: "))))))))(command "-layer" "of" LAY ""))(princ))
