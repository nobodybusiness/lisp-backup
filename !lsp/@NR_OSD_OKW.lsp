;renumeracja wszystkich oznaczen OKW_ na kolejne od zadanego
(defun c:@NR_OSD_OKW ()
	(vl-load-com)
  (setq ss (ssget))
  (setq i 0)
  (while (< i (sslength ss))
    (setq $VAL 0)
    (setq $ent (ssname ss i))
    (setq $name "none")
    (setq $name (cdr (assoc '0 (entget $ent))))
    (while (not (equal $name "SEQEND"))  ;NAZWA PROJEKTU
      (setq $LST (entget $ent))
      (setq $attag (cdr (assoc '2 $LST)))
      (setq $attag (strcase $attag))
      (if (= $attag "OSD")
        (progn
          (setq insideString (nth 2 (assoc '1 $LST)))
					(setq test (strcat insideString ""))
          ;(setq newStringInside (vl-string-subst "xxxxxx" "OKW_" newStringInside))
          ;(setq $VAL (subst (cons 1 newStringInside) (assoc '1 $LST) $LST))
          ;(entmod $VAL)
          ;(entupd $ent)
        )
      )
      (setq $ent (entnext $ent))
      (setq $name (cdr (assoc '0 (entget $ent))))
    )
    (setq i (+ i 1))
  )
)
