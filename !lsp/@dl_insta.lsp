;zczytanie dlugosci z blokow + dodanie budynkowych
(defun @dl_insta ()
  (vl-load-com)
  (setq $blk nil)
  (setq $blk (ssget '((0 . "INSERT") (2 . "dl_linni"))))
  (setq $i 0)
  (setq $blk_length (sslength $blk))
  (setq $VAL 0)
  (while (< $i $blk_length)
    (setq $ent (ssname $blk $i))
    (setq $name "none")
    (setq $name (cdr (assoc '0 (entget $ent))))
    (while (not (equal $name "SEQEND"))
      (setq $LST (entget $ent))
      (setq $attag (cdr (assoc '2 $LST)))
      (setq $attag (strcase $attag))
      (if (= $attag "DL")
        (setq $VAL_ZM (CDR (assoc 1 $LST)))
      )
      (setq $ent (entnext $ent))
      (setq $name (cdr (assoc '0 (entget $ent))))
    )
    (setq $VAL_ZM (atoi $VAL_ZM))
    (setq $VAL (+ $VAL $VAL_ZM))
    (setq $i (+ 1 $i))
  )
  (print $VAL)
  (setq $zapas (getint "Ile po budynku:"))
  (setq $val (+ $val $zapas))
  (print $VAL)
  (princ)
)
(defun c:sui ()
  (vl-load-com)
  (setq $blk nil)
  (setq $blk (ssget '((0 . "INSERT") (2 . "dl_linni"))))
  (setq $i 0)
  (setq $blk_length (sslength $blk))
  (setq $VAL 0)
  (while (< $i $blk_length)
    (setq $ent (ssname $blk $i))
    (setq $name "none")
    (setq $name (cdr (assoc '0 (entget $ent))))
    (while (not (equal $name "SEQEND"))
      (setq $LST (entget $ent))
      (setq $attag (cdr (assoc '2 $LST)))
      (setq $attag (strcase $attag))
      (if (= $attag "DL")
        (setq $VAL_ZM (CDR (assoc 1 $LST)))
      )
      (setq $ent (entnext $ent))
      (setq $name (cdr (assoc '0 (entget $ent))))
    )
    (setq $VAL_ZM (atoi $VAL_ZM))
    (setq $VAL (+ $VAL $VAL_ZM))
    (setq $i (+ 1 $i))
  )
	(setq $VAL (+(fix(* $VAL 1.1)) 1))
  (print $VAL)
  (setq $zapas (getint "Ile zapasu:"))
  (setq $val (+ $val $zapas))
  (print $VAL)
	(setq $bud_inst (getint "Budynkowa inst."))
	(setq $val (+ $val $bud_inst))
  (print $VAL)
  (princ)
)
